; SHX 不在エラー経路の検証図面生成: 実在しない SHX フォントを指すスタイルの DBText を1つ作る。
(defun c:GENMISSINGSHX ( / )
  (if (not (tblsearch "STYLE" "MISSING_SHX"))
    (entmake (list '(0 . "STYLE") '(100 . "AcDbSymbolTableRecord")
                   '(100 . "AcDbTextStyleTableRecord")
                   '(2 . "MISSING_SHX") '(3 . "cadpeta_missing_font.shx") '(4 . "")
                   '(70 . 0) '(40 . 0.0) '(41 . 1.0) '(50 . 0.0)
                   '(71 . 0) '(42 . 2.5))))
  (entmake (list '(0 . "TEXT") '(100 . "AcDbEntity") '(8 . "0")
                 '(100 . "AcDbText") '(10 5.0 5.0 0.0) '(40 . 5.0)
                 '(1 . "Missing Shx Test") '(50 . 0.0) '(41 . 1.0)
                 '(51 . 0.0) '(7 . "MISSING_SHX") '(71 . 0) '(72 . 0)
                 '(11 0.0 0.0 0.0) '(210 0.0 0.0 1.0)))
  (princ)
)
(princ)

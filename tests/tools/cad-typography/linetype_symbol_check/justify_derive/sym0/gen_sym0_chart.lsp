(defun c:GENSYM0 ( / y)
  (command "-linetype" "L" "JP15SYM" "C:\\Users\\wk\\AppData\\Local\\Temp\\cadpeta_p3b_ltjust\\sym0\\jp15sym.lin" "")
  (setvar "LTSCALE" 1.0)
  (setvar "CELTSCALE" 1.0)
  (command "-linetype" "S" "JP15SYM" "")
  (setq y 0)
  (foreach len (list 15 20 26 37 45 60 100)
    (command "_LINE" (list 0 y) (list len y) "")
    (setq y (+ y 20))
  )
  (command "-linetype" "S" "BYLAYER" "")
  (princ)
)
(c:GENSYM0)
